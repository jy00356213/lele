(defun c:xx()

(setq GDSJ '(
	     (400 0.04 0.4 0.1)
	     (500 0.05 0.5 0.1)
	     (600 0.06 0.6 0.11)
	     (700 0.07 0.7 0.11)
	     (800 0.08 0.8 0.12)
	     (900 0.09 0.9 0.13)
	     (1000 0.1 1.0 0.14)
	     (1100 0.11 1.1 0.143)
	     (1200 0.12 1.2 0.16)
	     (1350 0.135 1.35 0.173)
	     (1400 0.14 1.4 0.18)
	     (1500 0.15 1.5 0.188)
	     (1600 0.16 1.6 0.2)
	     (1650 0.165 1.65 0.21)
	     (1800 0.18 1.8 0.225)
	     (2000 0.20 2.0 0.26)
	     (2200 0.22 2.2 0.278)
	     (2400 0.24 2.4 0.3)
	     (2600 0.26 2.6 0.33)
	     (2800 0.28 2.8 0.353)
	     (3000 0.3 3.0 0.375)
	    )
)


(setq FG '(
                   (11000 (1 0.12 0.26))
                   (11200 (1 0.14 0.28) (1.2 0.14 0.28))
                   (11400 (1 0.14 0.28) (1.2 0.14 0.28) (1.4 0.14 0.28))
                   (11600 (1 0.16 0.3) (1.2 0.16 0.3) (1.4 0.16 0.3) (1.6 0.16 0.3))
                   (11800 (1 0.18 0.32) (1.2 0.18 0.32) (1.4 0.18 0.32) (1.6 0.18 0.32) (1.8 0.18 0.32))
	   (12000 (1 0.18 0.32) (1.2 0.18 0.32) (1.4 0.18 0.32) (1.6 0.18 0.32) (1.8 0.18 0.32) (2 0.18 0.32))
	   (12200 (1 0.2 0.34) (1.2 0.2 0.34) (1.4 0.2 0.34) (1.6 0.2 0.34) (1.8 0.2 0.34) (2 0.2 0.34) (2.2 0.2 0.34))
                   (12400 (1 0.22 0.36) (1.2 0.22 0.36) (1.4 0.22 0.36) (1.6 0.22 0.36) (1.8 0.22 0.36) (2 0.22 0.36) (2.2 0.22 0.36) (2.4 0.22 0.36) (3.0 0.26 0.4))
	   (12600 (1 0.22 0.36) (1.2 0.22 0.36) (1.4 0.22 0.36) (1.6 0.22 0.36) (1.8 0.22 0.36) (2 0.22 0.36) (2.2 0.22 0.36) (2.4 0.22 0.36) (2.6 0.22 0.36))
	   (12800 (1 0.24 0.38) (1.2 0.24 0.38) (1.4 0.24 0.38) (1.6 0.24 0.38) (1.8 0.24 0.38) (2 0.24 0.38) (2.2 0.24 0.38) (2.4 0.24 0.38) (2.6 0.24 0.38) (2.8 0.24 0.38) (3.2 0.40 0.46))
	   (13000 (1 0.26 0.4) (1.2 0.26 0.4) (1.4 0.26 0.4) (1.6 0.26 0.4) (1.8 0.26 0.4) (2 0.26 0.4) (2.2 0.26 0.4) (2.4 0.26 0.4) (2.6 0.26 0.4) (2.8 0.26 0.4) (3.0 0.40 0.46))
	   (13200 (1 0.28 0.4) (1.2 0.28 0.4) (1.4 0.28 0.4) (1.6 0.28 0.4) (1.8 0.28 0.4) (2 0.28 0.4) (2.2 0.28 0.4) (2.4 0.28 0.4) (2.6 0.28 0.4) (2.8 0.28 0.4))
	   (13400 (1 0.28 0.42) (1.2 0.28 0.42) (1.4 0.28 0.42) (1.6 0.28 0.42) (1.8 0.28 0.42) (2 0.28 0.42) (2.2 0.28 0.42) (2.4 0.28 0.42) (2.6 0.28 0.42) (2.8 0.28 0.42))
	   (13600 (1 0.3 0.42) (1.2 0.3 0.42) (1.4 0.3 0.42) (1.6 0.3 0.42) (1.8 0.3 0.42) (2 0.3 0.42) (2.2 0.3 0.42) (2.4 0.3 0.42) (2.6 0.3 0.42) (2.8 0.3 0.42))
	   (13800 (1 0.32 0.44) (1.2 0.32 0.44) (1.4 0.32 0.44) (1.6 0.32 0.44) (1.8 0.32 0.44) (2 0.32 0.44) (2.2 0.32 0.44) (2.4 0.32 0.44) (2.6 0.32 0.44) (2.8 0.32 0.44))
	   (14000 (1 0.32 0.46) (1.2 0.32 0.46) (1.4 0.32 0.46) (1.6 0.32 0.46) (1.8 0.32 0.46) (2 0.40 0.46) (2.2 0.40 0.46) (2.4 0.40 0.46) (2.6 0.40 0.46) (2.8 0.40 0.46) (3.2 0.40 0.46))
                   (14200 (1 0.32 0.46) (1.2 0.32 0.46) (1.4 0.32 0.46) (1.6 0.32 0.46) (1.8 0.32 0.46) (2 0.40 0.46) (2.2 0.40 0.46) (2.4 0.40 0.46) (2.6 0.40 0.46) (2.8 0.40 0.46) (3.2 0.40 0.46))
	)
)
					;(setq GJ (getreal "请输入管径:"))
					;(setq X (CDR (setq X (assoc GJ FG))))
					;(setq HIGH (getreal "请输入高度:"))
					;(setq Y (assoc HIGH X))

					; 第一步  建立数据库


(if (not JLB) (setq JLB '()))	; 初始化记录表
(if (not BH) (setq BH 0))		; 仅在首次初始化编号
  (setq NEXT (1+ BH))			; 预分配编号，标注成功后才保存
  (setq N-str (strcat (itoa NEXT) "、\n"))	; 编号字符串
  (setq GJ (getreal "\n请输入管径:"))
  (setq NDG (getreal "请输入管内底高程:"))

					; 第二步  计算



  (setq X (assoc GJ GDSJ))		;查询GDSJ 表
					;(setq y (assoc GJ FG)); 查询FG 表
					;获取对应管径数据  为逻辑判断做准备

  (setq ucs-ang (angle '(0 0 0) (trans '(1 0 0) 1 0))) ; UCS旋转角度

  (IF (= X nil)
    (progn
           (setq K (assoc GJ GDSJ))
           (setq K (CDR (setq K (assoc GJ FG)))) ;去掉第一个元素后取得的表
           (setq HIGH (getreal "请输入高度:"))
           (setq Z (assoc HIGH K))		;查找高度对应的数据
           (setq GWD (+ NDG (nth 0 Z) (nth 1 Z))) ; 计算管外顶
           (setq GWDD (- NDG (nth 2 Z)))	; 计算管外底
           (setq GJ1 (substr(rtos GJ 2 2) 2 ))		; 得到管径字符串
           (setq strhigh (rtos (* HIGH 1000) 2 2));得到HIGH的字符串，和上面组成管径的形式
           (setq GWD (rtos GWD 2 2))		;转字符串
           (setq NDG (rtos NDG 2 2))		;转字符串
           (setq GWDD (rtos GWDD 2 2))	;转字符串
           (setq output (strcat
		               N-str
		               (strcat "     管外顶" GWD)
		               (strcat "\n" GJ1 "x" strhigh "管内底" NDG)
		               (strcat "\n" "  管外底" GWDD)
                         )
            )

         (entmake (list '(0 . "MTEXT")
		     '(100 . "AcDbEntity")
		     '(100 . "AcDbMText")
		     '(7 . "Standard")
		     (cons 8 "zl-重力流管底高程")
		     (cons 410 "Model")
		      (cons 1 output)
		      (cons 10 (trans (getpoint) 1 0))
		      (cons 50 ucs-ang)
		     '(40 . 2.5)
		     '(72 . 1)
		     '(73 . 1)
                   )
          )
         (setq BH NEXT)		; 标注成功，确认编号
         (setq JLB (cons (list (itoa NEXT) (strcat GJ1 "x" strhigh) NDG GWD GWDD) JLB))
     )
  			;如果不等于 则执行下面函数

    (progn
       (setq X (assoc GJ GDSJ))
       (setq GWD (+ NDG (nth 1 X) (nth 2 X))) ; 计算管外顶
       (setq GWDD (- NDG (nth 1 X) (nth 3 X))) ; 计算管外底
       (setq GJ1 (nth 0 X))		; 得到管径字符串
       (setq GJ1 (rtos GJ1 2 1))		;转字符串
       (setq GWD (rtos GWD 2 2))		;转字符串
       (setq NDG (rtos NDG 2 2))		;转字符串
       (setq GWDD (rtos GWDD 2 2))	;转字符串
       (setq output (strcat
		           N-str
		           (strcat "     管外顶" GWD)
			   (strcat "\n" "DN" GJ1 "管内底" NDG)
			   (strcat "\n" " 管外底" GWDD)
		     )
        )

        (entmake (list '(0 . "MTEXT")
		     '(100 . "AcDbEntity")
		     '(100 . "AcDbMText")
		     '(7 . "Standard")
		     (cons 8 "zl-重力流管底高程")
		     (cons 410 "Model")
		     (cons 1 output)
		     (cons 10 (trans (getpoint) 1 0))
		     (cons 50 ucs-ang)
		     '(40 . 2.5)
		     '(72 . 1)
		     '(73 . 1)
	          )
        )
        (setq BH NEXT)		; 标注成功，确认编号
        (setq JLB (cons (list (itoa NEXT) (strcat "DN" GJ1) NDG GWD GWDD) JLB))
      )

    )
  (show-jlb)			; 自动显示汇总表
)
(defun show-jlb ()
  (if (not JLB)
    (princ "
没有记录，请先运行 XX 标注。")
    (progn
      (textscr)
      (princ "
==========================================")
      (princ "
 编号 | 管径       | 管内底  | 管外顶  | 管外底")
      (princ "
------------------------------------------")
      (foreach row (reverse JLB)
        (princ (strcat "
  " (nth 0 row) "  | " (nth 1 row) "  | " (nth 2 row) "  | " (nth 3 row) "  | " (nth 4 row)))
      )
      (princ "
==========================================")
      (princ (strcat "
共 " (itoa (length JLB)) " 条记录"))
    )
  )
  (princ)
)

(defun c:BBB ()
  (show-jlb)
)
(defun c:DC ()
  (if (not JLB)
    (princ "
没有记录，请先运行 XX 标注。")
    (progn
      (setq fname (getfiled "导出 CSV" "" "csv" 1))
      (if fname
        (progn
          (setq f (open fname "w"))
          (write-line "编号,管径,管内底,管外顶,管外底" f)
          (foreach row (reverse JLB)
            (write-line
              (strcat (nth 0 row) "," (nth 1 row) "," (nth 2 row) "," (nth 3 row) "," (nth 4 row))
              f
            )
          )
          (close f)
          (princ (strcat "
已导出到: " fname))
          (command "_.start" fname)
        )
      )
    )
  )
  (princ)
)

    ;)					;如果这里有个括号,则上面的循环去掉


					;第叁步  第一段 在表一怎么查
