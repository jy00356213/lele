(defun c:xx()

(setq GDSJ '(
	     (400 0.04 0.4 0.1)
	     (500 0.05 0.5 0.1)
	     (600 0.06 0.6 0.11)
	     (700 0.07 0.7 0.11)
	     (800 0.08 0.8 0.12)
	     (900 0.09 0.9 0.13)
	     (1000 0.1 1.0 0.14)
	     (1100 0.11 1.1 0.143)
	     (1200 0.12 1.2 0.16)
	     (1350 0.135 1.35 0.173)
	     (1400 0.14 1.4 0.18)
	     (1500 0.15 1.5 0.188)
	     (1600 0.16 1.6 0.2)
	     (1650 0.165 1.65 0.21)
	     (1800 0.18 1.8 0.225)
	     (2000 0.20 2.0 0.26)
	     (2200 0.22 2.2 0.278)
	     (2400 0.24 2.4 0.3)
	     (2600 0.26 2.6 0.33)
	     (2800 0.28 2.8 0.353)
	     (3000 0.3 3.0 0.375)
	    )
)


(setq FG '(
                   (11000 (1 0.12 0.26))
                   (11200 (1 0.14 0.28) (1.2 0.14 0.28))
                   (11400 (1 0.14 0.28) (1.2 0.14 0.28) (1.4 0.14 0.28))
                   (11600 (1 0.16 0.3) (1.2 0.16 0.3) (1.4 0.16 0.3) (1.6 0.16 0.3))
                   (11800 (1 0.18 0.32) (1.2 0.18 0.32) (1.4 0.18 0.32) (1.6 0.18 0.32) (1.8 0.18 0.32))
	   (12000 (1 0.18 0.32) (1.2 0.18 0.32) (1.4 0.18 0.32) (1.6 0.18 0.32) (1.8 0.18 0.32) (2 0.18 0.32))
	   (12200 (1 0.2 0.34) (1.2 0.2 0.34) (1.4 0.2 0.34) (1.6 0.2 0.34) (1.8 0.2 0.34) (2 0.2 0.34) (2.2 0.2 0.34))
                   (12400 (1 0.22 0.36) (1.2 0.22 0.36) (1.4 0.22 0.36) (1.6 0.22 0.36) (1.8 0.22 0.36) (2 0.22 0.36) (2.2 0.22 0.36) (2.4 0.22 0.36) (3.0 0.26 0.4))
	   (12600 (1 0.22 0.36) (1.2 0.22 0.36) (1.4 0.22 0.36) (1.6 0.22 0.36) (1.8 0.22 0.36) (2 0.22 0.36) (2.2 0.22 0.36) (2.4 0.22 0.36) (2.6 0.22 0.36))
	   (12800 (1 0.24 0.38) (1.2 0.24 0.38) (1.4 0.24 0.38) (1.6 0.24 0.38) (1.8 0.24 0.38) (2 0.24 0.38) (2.2 0.24 0.38) (2.4 0.24 0.38) (2.6 0.24 0.38) (2.8 0.24 0.38) (3.2 0.40 0.46))
	   (13000 (1 0.26 0.4) (1.2 0.26 0.4) (1.4 0.26 0.4) (1.6 0.26 0.4) (1.8 0.26 0.4) (2 0.26 0.4) (2.2 0.26 0.4) (2.4 0.26 0.4) (2.6 0.26 0.4) (2.8 0.26 0.4) (3.0 0.40 0.46))
	   (13200 (1 0.28 0.4) (1.2 0.28 0.4) (1.4 0.28 0.4) (1.6 0.28 0.4) (1.8 0.28 0.4) (2 0.28 0.4) (2.2 0.28 0.4) (2.4 0.28 0.4) (2.6 0.28 0.4) (2.8 0.28 0.4))
	   (13400 (1 0.28 0.42) (1.2 0.28 0.42) (1.4 0.28 0.42) (1.6 0.28 0.42) (1.8 0.28 0.42) (2 0.28 0.42) (2.2 0.28 0.42) (2.4 0.28 0.42) (2.6 0.28 0.42) (2.8 0.28 0.42))
	   (13600 (1 0.3 0.42) (1.2 0.3 0.42) (1.4 0.3 0.42) (1.6 0.3 0.42) (1.8 0.3 0.42) (2 0.3 0.42) (2.2 0.3 0.42) (2.4 0.3 0.42) (2.6 0.3 0.42) (2.8 0.3 0.42))
	   (13800 (1 0.32 0.44) (1.2 0.32 0.44) (1.4 0.32 0.44) (1.6 0.32 0.44) (1.8 0.32 0.44) (2 0.32 0.44) (2.2 0.32 0.44) (2.4 0.32 0.44) (2.6 0.32 0.44) (2.8 0.32 0.44))
	   (14000 (1 0.32 0.46) (1.2 0.32 0.46) (1.4 0.32 0.46) (1.6 0.32 0.46) (1.8 0.32 0.46) (2 0.40 0.46) (2.2 0.40 0.46) (2.4 0.40.46) (2.6 0.40 0.46) (2.8 0.40 0.46) (3.2 0.40 0.46))
                   (14200 (1 0.32 0.46) (1.2 0.32 0.46) (1.4 0.32 0.46) (1.6 0.32 0.46) (1.8 0.32 0.46) (2 0.40 0.46) (2.2 0.40 0.46) (2.4 0.40.46) (2.6 0.40 0.46) (2.8 0.40 0.46) (3.2 0.40 0.46))
	)
)
					;(setq GJ (getreal "输入管径:"))
					;(setq X (CDR (setq X (assoc GJ FG))))
					;(setq HIGH (getreal "输入高度:"))
					;(setq Y (assoc HIGH X))

					; 第一部分  构建数据库


(repeat	100
  (setq GJ (getreal "输入管径:"))
  (setq NDG (getreal "输入管内底高程:"))

					; 第二部分  输入



  (setq X (assoc GJ GDSJ))		;查找GDSJ 表
					;(setq y (assoc GJ FG)); 查找FG 表
					;调取相应管径的数据  为逻辑判断做准备


  (IF (= X nil)
    (progn
           (setq K (assoc GJ GDSJ))
           (setq K (CDR (setq K (assoc GJ FG)))) ;去掉第一个元素后，取得的表
           (setq HIGH (getreal "输入高度:"))
           (setq Z (assoc HIGH K))		;查找高度对应的数据
           (setq GWD (+ NDG (nth 0 Z) (nth 1 Z))) ; 计算管外顶
           (setq GWDD (- NDG (nth 2 Z)))	; 计算管外底
           (setq GJ1 (substr(rtos GJ 2 2) 2 ))		; 得到管径字符型
           (setq strhigh (rtos (* HIGH 1000) 2 2));得到HIGH的字符型，并把它变成管径的形式
           (setq GWD (rtos GWD 2 2))		;转化字符型
           (setq NDG (rtos NDG 2 2))		;转化字符型
           (setq GWDD (rtos GWDD 2 2))	;转化字符型
           (setq output (strcat
		               (strcat "     管外顶" GWD)
		               (strcat "\n" GJ1 "x" strhigh "管内底" NDG)
		               (strcat "\n" "  管外底" GWDD)
                         )
            )
 
         (entmake (list '(0 . "MTEXT")
		     '(100 . "AcDbEntity")
		     '(100 . "AcDbMText")
		     '(7 . "Standard")
		      (cons 1 output)
		      (cons 10 (getpoint))
		     '(40 . 2.5)
		     '(72 . 1)
		     '(73 . 1)
                   )
          )
     )
      			;如果=空 按方沟计算

    (progn
       (setq X (assoc GJ GDSJ))
       (setq GWD (+ NDG (nth 1 X) (nth 2 X))) ; 计算管外顶
       (setq GWDD (- NDG (nth 1 X) (nth 3 X))) ; 计算管外底
       (setq GJ1 (nth 0 X))		; 得到管径字符型
       (setq GJ1 (rtos GJ1 2 1))		;转化字符型
       (setq GWD (rtos GWD 2 2))		;转化字符型
       (setq NDG (rtos NDG 2 2))		;转化字符型
       (setq GWDD (rtos GWDD 2 2))	;转化字符型
       (setq output (strcat
		           (strcat "     管外顶" GWD)
			   (strcat "\n" "DN" GJ1 "管内底" NDG)
			   (strcat "\n" " 管外底" GWDD)
		     )
        )

        (entmake (list '(0 . "MTEXT")
		     '(100 . "AcDbEntity")
		     '(100 . "AcDbMText")
		     '(7 . "Standard")
		     (cons 1 output)
		     (cons 10 (getpoint))
		     '(40 . 2.5)
		     '(72 . 1)
		     '(73 . 1)
	          )
        )
      )

    )
  )
)
  
    ;)					;如果不等于空,按圆管去计算
 
  






					;第三部分 第一块  在表一中么？
