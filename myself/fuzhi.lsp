;;; fuzhi.lsp —— 给管线赋属性
;;; 命令 FZ：赋值（管线类型+规模 → 自动查结构参数）
;;; 命令 CX：查询

(regapp "ZL_PROP")

;;; ========== 结构参数数据库 ==========

;; 标准管径表 GDSJ：(管径 壁厚 管外高 基础厚)
(setq GDSJ '(
    (400 0.04 0.4 0.1)
    (500 0.05 0.5 0.1)
    (600 0.06 0.6 0.11)
    (700 0.07 0.7 0.11)
    (800 0.08 0.8 0.12)
    (900 0.09 0.9 0.13)
    (1000 0.1 1.0 0.14)
    (1100 0.11 1.1 0.143)
    (1200 0.12 1.2 0.16)
    (1350 0.135 1.35 0.173)
    (1400 0.14 1.4 0.18)
    (1500 0.15 1.5 0.188)
    (1600 0.16 1.6 0.2)
    (1650 0.165 1.65 0.21)
    (1800 0.18 1.8 0.225)
    (2000 0.20 2.0 0.26)
    (2200 0.22 2.2 0.278)
    (2400 0.24 2.4 0.3)
    (2600 0.26 2.6 0.33)
    (2800 0.28 2.8 0.353)
    (3000 0.3 3.0 0.375)
))

;; 非标管径表 FG：(管径 (高度 壁厚 基础厚) ...)
(setq FG '(
    (11000 (1 0.12 0.26))
    (11200 (1 0.14 0.28) (1.2 0.14 0.28))
    (11400 (1 0.14 0.28) (1.2 0.14 0.28) (1.4 0.14 0.28))
    (11600 (1 0.16 0.3) (1.2 0.16 0.3) (1.4 0.16 0.3) (1.6 0.16 0.3))
    (11800 (1 0.18 0.32) (1.2 0.18 0.32) (1.4 0.18 0.32) (1.6 0.18 0.32) (1.8 0.18 0.32))
    (12000 (1 0.18 0.32) (1.2 0.18 0.32) (1.4 0.18 0.32) (1.6 0.18 0.32) (1.8 0.18 0.32) (2 0.18 0.32))
    (12200 (1 0.2 0.34) (1.2 0.2 0.34) (1.4 0.2 0.34) (1.6 0.2 0.34) (1.8 0.2 0.34) (2 0.2 0.34) (2.2 0.2 0.34))
    (12400 (1 0.22 0.36) (1.2 0.22 0.36) (1.4 0.22 0.36) (1.6 0.22 0.36) (1.8 0.22 0.36) (2 0.22 0.36) (2.2 0.22 0.36) (2.4 0.22 0.36) (3.0 0.26 0.4))
    (12600 (1 0.22 0.36) (1.2 0.22 0.36) (1.4 0.22 0.36) (1.6 0.22 0.36) (1.8 0.22 0.36) (2 0.22 0.36) (2.2 0.22 0.36) (2.4 0.22 0.36) (2.6 0.22 0.36))
    (12800 (1 0.24 0.38) (1.2 0.24 0.38) (1.4 0.24 0.38) (1.6 0.24 0.38) (1.8 0.24 0.38) (2 0.24 0.38) (2.2 0.24 0.38) (2.4 0.24 0.38) (2.6 0.24 0.38) (2.8 0.24 0.38) (3.2 0.40 0.46))
    (13000 (1 0.26 0.4) (1.2 0.26 0.4) (1.4 0.26 0.4) (1.6 0.26 0.4) (1.8 0.26 0.4) (2 0.26 0.4) (2.2 0.26 0.4) (2.4 0.26 0.4) (2.6 0.26 0.4) (2.8 0.26 0.4) (3.0 0.40 0.46))
    (13200 (1 0.28 0.4) (1.2 0.28 0.4) (1.4 0.28 0.4) (1.6 0.28 0.4) (1.8 0.28 0.4) (2 0.28 0.4) (2.2 0.28 0.4) (2.4 0.28 0.4) (2.6 0.28 0.4) (2.8 0.28 0.4))
    (13400 (1 0.28 0.42) (1.2 0.28 0.42) (1.4 0.28 0.42) (1.6 0.28 0.42) (1.8 0.28 0.42) (2 0.28 0.42) (2.2 0.28 0.42) (2.4 0.28 0.42) (2.6 0.28 0.42) (2.8 0.28 0.42))
    (13600 (1 0.3 0.42) (1.2 0.3 0.42) (1.4 0.3 0.42) (1.6 0.3 0.42) (1.8 0.3 0.42) (2 0.3 0.42) (2.2 0.3 0.42) (2.4 0.3 0.42) (2.6 0.3 0.42) (2.8 0.3 0.42))
    (13800 (1 0.32 0.44) (1.2 0.32 0.44) (1.4 0.32 0.44) (1.6 0.32 0.44) (1.8 0.32 0.44) (2 0.32 0.44) (2.2 0.32 0.44) (2.4 0.32 0.44) (2.6 0.32 0.44) (2.8 0.32 0.44))
    (14000 (1 0.32 0.46) (1.2 0.32 0.46) (1.4 0.32 0.46) (1.6 0.32 0.46) (1.8 0.32 0.46) (2 0.40 0.46) (2.2 0.40 0.46) (2.4 0.40 0.46) (2.6 0.40 0.46) (2.8 0.40 0.46) (3.2 0.40 0.46))
    (14200 (1 0.32 0.46) (1.2 0.32 0.46) (1.4 0.32 0.46) (1.6 0.32 0.46) (1.8 0.32 0.46) (2 0.40 0.46) (2.2 0.40 0.46) (2.4 0.40 0.46) (2.6 0.40 0.46) (2.8 0.40 0.46) (3.2 0.40 0.46))
))

;; 管线类型简称 → 全称
(setq LX-ALIST '(
    ("WS" . "污水管")
    ("YS" . "雨水管")
    ("JS" . "给水管")
    ("RQ" . "燃气管")
    ("DL" . "电力管")
    ("TX" . "通信管")
    ("RL" . "热力管")
    ("ZL" . "重力流管道")
))

;;; ========== 结构参数查询 ==========
(defun chaxun (gj / X K Z)
  ;; 先查标准管径
  (setq X (assoc gj GDSJ))
  (if X
    ;; 标准管：返回 (壁厚 管外高 基础厚 "标准")
    (list (nth 1 X) (nth 2 X) (nth 3 X) "标准")
    ;; 非标：查 FG，需选高度
    (progn
      (setq K (cdr (assoc gj FG)))
      (if K
        (progn
          (princ "\n非标管径，可选高度：")
          (foreach item K (princ (strcat "\n  " (rtos (nth 0 item) 2 1) "m")))
          (setq high (getreal "\n选择高度(m)："))
          (setq Z (assoc high K))
          (if Z
            (list (nth 1 Z) (nth 2 Z) high "非标")
            (progn (princ "\n未找到该高度！") nil)
          )
        )
        (progn (princ "\n管径未在数据库中！") nil)
      )
    )
  )
)

;;; ========== 命令：FZ 赋值 ==========
(defun c:FZ ()
  (setq ent (car (entsel "\n选择管线对象：")))
  (if (not ent)
    (princ "\n未选择对象。")
    (progn
      ;; 第一步：选择管线种类
      (initget "WS YS JS RQ DL TX RL ZL")
      (setq lx-key (getkword "\n管线种类 [WS污水/YS雨水/JS给水/RQ燃气/DL电力/TX通信/RL热力/ZL重力流]："))
      (if (not lx-key)
        (princ "\n未选择种类。")
        (progn
          (setq lx-name (cdr (assoc lx-key LX-ALIST)))

          ;; 第二步：输入管径
          (setq gj (getint "\n管径（如600、1200、14000）："))
          (if (not gj)
            (princ "\n未输入管径。")
            (progn
              ;; 第三步：查结构参数
              (setq csjg (chaxun gj))
              (if (not csjg)
                (princ "\n未能获取结构参数。")
                (progn
                  (setq bihou  (nth 0 csjg))  ; 壁厚
                  (setq gaodu  (nth 1 csjg))  ; 管外高
                  (setq jichu  (nth 2 csjg))  ; 基础厚
                  (setq biaozhun (nth 3 csjg)) ; 标准/非标

                  (princ (strcat "\n结构参数：壁厚=" (rtos bihou 2 3)
                                 " 管外高=" (rtos gaodu 2 2)
                                 " 基础厚=" (rtos jichu 2 3)
                                 " [" biaozhun "]"))

                  ;; 第四步：管线名称（可自动生成）
                  (setq default-name (strcat lx-name "DN" (itoa gj)))
                  (princ (strcat "\n默认管线名称：" default-name))
                  (setq name (getstring T "\n管线名称（回车使用默认）："))
                  (if (= name "") (setq name default-name))

                  ;; 第五步：管外顶高程（可留空，以后推算）
                  (initget 6)
                  (setq elev (getreal "\n管外顶高程（留空=待推算）："))

                  ;; 第六步：地面高程
                  (initget 6)
                  (setq ground (getreal "\n地面高程（留空=未知）："))

                  ;; 第七步：写入 XData
                  ;; 格式：名称|类型|管径|管顶高程|地面高程|壁厚|管外高|基础厚|标准/非标
                  (setq xdata (list -3
                    (list "ZL_PROP"
                      (cons 1000 name)          ; 管线名称
                      (cons 1000 lx-name)       ; 管线类型
                      (cons 1040 gj)            ; 管径
                      (cons 1040 (if elev elev 0.0))     ; 管外顶高程
                      (cons 1040 (if ground ground 0.0)) ; 地面高程
                      (cons 1040 bihou)         ; 壁厚
                      (cons 1040 gaodu)         ; 管外高/高度
                      (cons 1040 jichu)         ; 基础厚
                      (cons 1000 biaozhun)      ; 标准/非标
                    )
                  ))
                  (entmod (append (entget ent) (list xdata)))

                  (princ (strcat "\n✓ 已赋值 -> " name
                                 " | 类型=" lx-name
                                 " | 管径=" (itoa gj)
                                 (if elev (strcat " | 管顶=" (rtos elev 2 2)) "")
                                 (if ground (strcat " | 地面=" (rtos ground 2 2)) "")))
                )
              )
            )
          )
        )
      )
    )
  )
  (princ)
)

;;; ========== 命令：CX 查询 ==========
(defun c:CX ()
  (setq ent (car (entsel "\n选择要查询的管线：")))
  (if ent
    (progn
      (setq ed (entget ent '("ZL_PROP")))
      (setq xd (assoc -3 ed))
      (if xd
        (progn
          (setq zl (cdr (assoc "ZL_PROP" (cdr xd))))
          (if zl
            (progn
              (setq zl-list (cdr zl))
              (princ (strcat "\n══════════════════════"
                             "\n管线名称：" (cdr (assoc 1000 zl-list))
                             "\n管线类型：" (cdr (assoc 1000 (member (cons 1000 "") zl-list)))  ; 第二个1000
                             ))
              ;; 简化输出
              (princ (strcat "\n══════════════════════"))
            )
            (princ "\n该对象没有 ZL 属性。")
          )
        )
        (princ "\n该对象没有 ZL 属性。")
      )
    )
  )
  (princ)
)

(princ "\n加载完成。FZ=赋值（选类型→管径→自动查参数）  CX=查询")
(princ)
